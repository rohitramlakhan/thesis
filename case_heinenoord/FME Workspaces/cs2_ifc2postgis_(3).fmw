FME workspace cs2_ifc2postgis_(3).fmw

Parameters:
- DestDataset_POSTGIS = case_heinenoord   # Connection
- SourceDataset_IFC = $(FME_MF_DIR)NAR_Heinenoordtunnel_simplified.ifc   # Source Industry Foundation Class (IFC) File(s)
- SourceDataset_IFC_3 = $(FME_MF_DIR)parcels_heinenoord.ifc   # Source Industry Foundation Class (IFC) File(s)

Readers:
- IFC_1: IFC from $(SourceDataset_IFC)
- IFC_2: IFC from $(SourceDataset_IFC_3)

Writers:
- POSTGIS_1: POSTGIS to $(DestDataset_POSTGIS)

Bookmark: IFC model - Heinenoordtunnel
IfcSpace (reader IFC_1)
    attributes: GlobalId char(22), Name string, Description string, ObjectType string, LongName string, CompositionType enumeration, InteriorOrExteriorSpace enumeration, ElevationWithFlooring real, Annotation geometry, Axis geometry, Body geometry, ifc_type_object_id string
    -> GeometryPropertyExtractor

Bookmark: Georeference
GeometryPropertyExtractor
    EXTRACTTYPE_PARAM = Traits
    PREFIX_EXTRACTED_TRAITS = Yes
    EXTRACTED -> GeometryPartExtractor
GeometryPartExtractor
    GQUERY:
      for $geom in //geometry
      where $geom/parent::geometry/@fme_geometry_type = 'IFMEAggregate'
      and $geom/@fme_geometry_name = 'Body'
      return number($geom/@fme_id)
    EXTRACTED -> Scaler
Scaler
    RASTER_SCALING = Extents
    SCALE_ORIGIN = 0,0
    TEXT_LOC_ONLY = Location and Size
    XSCALE = 0.001
    YSCALE = 0.001
    ZSCALE = 0.001
    SCALED -> LocalCoordinateSystemSetter
LocalCoordinateSystemSetter
    ORIGIN_CS = EPSG:28992
    ORIGIN_X = 4.511569
    ORIGIN_Y = 51.832915
    PROJECTION_TYPE = Equidistant (AZMED)
    PROJECTION_UNITS = Meters
    -> Offsetter
Offsetter
    MODE = Cartesian Coordinate
    XOFF = -12020
    YOFF = 2200
    ZOFF = 45
    OFFSET -> Aggregator
Aggregator
    ACCUM_ATTRS_NAME = Use Attributes From One Feature
    AGGREGATE_TYPE = Homogeneous Collection (If Possible)
    GROUP_BY = GlobalId
    MODE = Geometry - Assemble One Level
    SEP = ,
    AGGREGATE -> AttributeCreator

Bookmark: PostGIS
AttributeCreator
    ATTR_TABLE:
      SET_TO Name = @Value(GlobalId)
      SET_TO ObjectType = Tunnel
    -> AttributeManager
AttributeManager
    ATTR_TABLE:
      RENAME_SET_VALUE GlobalId > globalid
      RENAME_SET_VALUE Name > name
      RENAME_SET_VALUE Description > description
      RENAME_SET_VALUE ObjectType > objecttype
      RENAME_SET_VALUE CompositionType > compositiontype
      RENAME_SET_VALUE Annotation > annotation
      RENAME_SET_VALUE Axis > axis
      RENAME_SET_VALUE Body > body
    USER_EXPOSED_ATTRIBUTES = Tag
    -> tunnel_heinenoord (writer POSTGIS_1)
tunnel_heinenoord (writer POSTGIS_1)
    attributes: globalid char(22), name text, description text, objecttype text, compositiontype text, annotation text, axis text, body text, ifc_parent_id text, ifc_parent_unique_id text, ifc_type_object_id text, ifc_unique_id text

Bookmark: IFC model - Parcels
IfcSpace (reader IFC_2)
    attributes: GlobalId char(22), Name string, Description string, ObjectType string, LongName string, CompositionType enumeration, InteriorOrExteriorSpace enumeration, ElevationWithFlooring real, Annotation geometry, Axis geometry, Body geometry, ifc_type_object_id string
    -> AttributeManager_2

Bookmark: PostGIS
AttributeManager_2
    ATTR_TABLE:
      RENAME_SET_VALUE GlobalId > globalid
      RENAME_SET_VALUE Name > name
      RENAME_SET_VALUE Description > description
      RENAME_SET_VALUE LongName > longname
      RENAME_SET_VALUE ObjectType > objecttype
      RENAME_SET_VALUE CompositionType > compositiontype
      RENAME_SET_VALUE InteriorOrExteriorSpace > interiororexteriorspace
      RENAME_SET_VALUE ElevationWithFlooring > elevationwithflooring
      RENAME_SET_VALUE Annotation > annotation
      RENAME_SET_VALUE Axis > axis
      RENAME_SET_VALUE Body > body
    -> parcels_heinenoord (writer POSTGIS_1)
parcels_heinenoord (writer POSTGIS_1)
    attributes: globalid char(22), name text, description text, objecttype text, longname text, compositiontype text, interiororexteriorspace text, elevationwithflooring float8, annotation text, axis text, body text, ifc_parent_id text, ifc_parent_unique_id text, ifc_type_object_id text, ifc_unique_id text
