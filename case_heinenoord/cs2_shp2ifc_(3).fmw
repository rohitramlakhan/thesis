FME workspace cs2_shp2ifc_(3).fmw

Parameters:
- SourceDataset_SHAPEFILE = $(FME_MF_DIR)parcels_heinenoord.shp   # Source Esri Shapefile(s)
- DestDataset_IFC = $(FME_MF_DIR)parcels_heinenoord.ifc   # Destination Industry Foundation Class (IFC) File(s)

Readers:
- SHAPEFILE_1: SHAPEFILE from $(SourceDataset_SHAPEFILE)

Writers:
- IFC_1: IFC to $(DestDataset_IFC)

Bookmark: SHP model
parcels_heinenoord (reader SHAPEFILE_1)
    attributes: id varchar(254), identifica varchar(254), identifi_1 varchar(254), beginGeldi varchar(254), tijdstipRe varchar(254), volgnummer long, statusHist varchar(254), statusHi_1 varchar(254), kadastrale varchar(254), kadastra_1 varchar(254), sectie varchar(254), AKRKadastr varchar(254), AKRKadas_1 varchar(254), kadastra_2 double, soortGroot varchar(254), soortGro_1 varchar(254), perceelnum long, perceeln_1 double, perceeln_2 double, perceeln_3 double, perceeln_4 double, perceeln_5 double
    -> CommonLocalReprojector

Bookmark: Georeference
CommonLocalReprojector
    PROJECTION_TYPE = Equidistant (AZMED)
    VERTICAL_HANDLING = Ignore heights and leave them unchanged
    -> CoordinateSystemExtractor
CoordinateSystemExtractor
    CRDSYS_ATTR = _coordsys
    -> StringSearcher
StringSearcher
    CASE = no
    MATCHED_PARTS_ATTR = _matches
    MATCHED_RESULT_ATTR = _first_match
    REGEXP = _([-]*[\d]+[\.][\d]*)
    STRING_TO_SEARCH = @Value(_coordsys)
    MATCHED -> ElevationExtractor
ElevationExtractor
    ELE_ATTR = _elevation
    -> AttributeCreator
AttributeCreator
    ATTR_TABLE:
      SET_TO RefLatitude = @Value(_matches{1}.part)
      SET_TO RefLongitude = @Value(_matches{0}.part)
      SET_TO RefElevation = @Value(_elevation)
    -> AttributeExposer
AttributeExposer
    ATTR_LIST = fme_feature_type
    -> Extruder
    -> Sampler_4
    -> GeometryRemover
    -> Sampler
    -> Sampler_2
    -> Sampler_3

Bookmark: Site
Sampler
    RATE = 1
    SAMPLE_MODE = No
    SAMPLE_TYPE_LONG = First N Features
    SAMPLED -> IfcSite (writer IFC_1)
IfcSite (writer IFC_1)
    attributes: id varchar(254), identifica varchar(254), identifi_1 varchar(254), beginGeldi varchar(254), tijdstipRe varchar(254), volgnummer int, statusHist varchar(254), statusHi_1 varchar(254), kadastrale varchar(254), kadastra_1 varchar(254), sectie varchar(254), AKRKadastr varchar(254), AKRKadas_1 varchar(254), kadastra_2 number, soortGroot varchar(254), soortGro_1 varchar(254), perceelnum int, perceeln_1 number, perceeln_2 number, perceeln_3 number, perceeln_4 number, perceeln_5 number

Bookmark: Building
Sampler_2
    GROUP_BY = fme_feature_type
    RATE = 1
    SAMPLE_MODE = No
    SAMPLE_TYPE_LONG = First N Features
    SAMPLED -> AttributeCreator_2
AttributeCreator_2
    ATTR_TABLE = SET_TO ifc_id = Building
    -> IfcBuilding (writer IFC_1)
IfcBuilding (writer IFC_1)
    attributes: id varchar(254), identifica varchar(254), identifi_1 varchar(254), beginGeldi varchar(254), tijdstipRe varchar(254), volgnummer int, statusHist varchar(254), statusHi_1 varchar(254), kadastrale varchar(254), kadastra_1 varchar(254), sectie varchar(254), AKRKadastr varchar(254), AKRKadas_1 varchar(254), kadastra_2 number, soortGroot varchar(254), soortGro_1 varchar(254), perceelnum int, perceeln_1 number, perceeln_2 number, perceeln_3 number, perceeln_4 number, perceeln_5 number

Bookmark: Building Storey
Sampler_3
    GROUP_BY = fme_feature_type
    RATE = 1
    SAMPLE_MODE = No
    SAMPLE_TYPE_LONG = First N Features
    SAMPLED -> AttributeCreator_3
AttributeCreator_3
    ATTR_TABLE:
      SET_TO ifc_parent_id = Building
      SET_TO ifc_id = BuildingStorey
      SET_TO Name = Parcels
    -> IfcBuildingStorey (writer IFC_1)
IfcBuildingStorey (writer IFC_1)
    attributes: id varchar(254), identifica varchar(254), identifi_1 varchar(254), beginGeldi varchar(254), tijdstipRe varchar(254), volgnummer int, statusHist varchar(254), statusHi_1 varchar(254), kadastrale varchar(254), kadastra_1 varchar(254), sectie varchar(254), AKRKadastr varchar(254), AKRKadas_1 varchar(254), kadastra_2 number, soortGroot varchar(254), soortGro_1 varchar(254), perceelnum int, perceeln_1 number, perceeln_2 number, perceeln_3 number, perceeln_4 number, perceeln_5 number

Bookmark: Space
Extruder
    DIRECTION = Specified
    EXTRUSION_X = 0.0
    EXTRUSION_Y = 0.0
    EXTRUSION_Z = 200
    EXTRUDED -> Offsetter
Offsetter
    MODE = Cartesian Coordinate
    XOFF = 0
    YOFF = 0
    ZOFF = -100
    OFFSET -> GeometryPropertySetter
GeometryPropertySetter
    GEOM_NAME_FIELD = Body
    GQUERY:
      for $geom in //geometry
      where $geom/count(parent::geometry) = 0
      return number($geom/@fme_id)
    OVERWRITE_CHOICE = Yes
    SETTYPE_PARAM = Geometry Name
    SET -> Aggregator
Aggregator
    ACCUM_ATTRS_NAME = Merge Incoming Attributes
    AGGREGATE_TYPE = Homogeneous Collection (If Possible)
    GROUP_BY = identifi_1
    MODE = Geometry - Assemble One Level
    ORDERED = No
    SEP = ,
    AGGREGATE -> AttributeCreator__4
AttributeCreator__4
    ATTR_TABLE:
      SET_TO ifc_parent_id = BuildingStorey
      SET_TO Name = @Value(perceelnum)
      SET_TO ObjectType = Parcel
    -> IfcSpace (writer IFC_1)
IfcSpace (writer IFC_1)
    attributes: id varchar(254), identifica varchar(254), identifi_1 varchar(254), beginGeldi varchar(254), tijdstipRe varchar(254), volgnummer int, statusHist varchar(254), statusHi_1 varchar(254), kadastrale varchar(254), kadastra_1 varchar(254), sectie varchar(254), AKRKadastr varchar(254), AKRKadas_1 varchar(254), kadastra_2 number, soortGroot varchar(254), soortGro_1 varchar(254), perceelnum int, perceeln_1 number, perceeln_2 number, perceeln_3 number, perceeln_4 number, perceeln_5 number

Bookmark: Property Set
GeometryRemover
    -> AttributeCreator_5
AttributeCreator_5
    ATTR_TABLE:
      SET_TO ifc_property_set_name = Pset_SpaceCommon
      SET_TO Category = Parcel
    -> GeometryPropertySetter_2
GeometryPropertySetter_2
    OVERWRITE_CHOICE = Yes
    REMOVE_ATTRIBUTE = No
    SETTYPE_PARAM = Traits From Attributes
    SRC_ATTRS = ifc_property_set_name Category
    SET -> GeometryPropertySetter_3
GeometryPropertySetter_3
    GEOM_NAME_FIELD = IfcPropertySet
    OVERWRITE_CHOICE = Yes
    SETTYPE_PARAM = Geometry Name
    SET -> Aggregator
Sampler_4
    RATE = 1
    SAMPLE_MODE = No
    SAMPLE_TYPE_LONG = First N Features
    SAMPLED -> GeometryRemover_2
GeometryRemover_2
    -> IFCPropertySetDefinitionCreator
IFCPropertySetDefinitionCreator
    PROPERTIES_TABLE = Category IfcPropertySingleValue IfcLabel
    PSET_NAME = Pset_SpaceCommon
    -> PropertySetDefinition (writer IFC_1)
PropertySetDefinition (writer IFC_1)
    attributes: id varchar(254), identifica varchar(254), identifi_1 varchar(254), beginGeldi varchar(254), tijdstipRe varchar(254), volgnummer int, statusHist varchar(254), statusHi_1 varchar(254), kadastrale varchar(254), kadastra_1 varchar(254), sectie varchar(254), AKRKadastr varchar(254), AKRKadas_1 varchar(254), kadastra_2 number, soortGroot varchar(254), soortGro_1 varchar(254), perceelnum int, perceeln_1 number, perceeln_2 number, perceeln_3 number, perceeln_4 number, perceeln_5 number
