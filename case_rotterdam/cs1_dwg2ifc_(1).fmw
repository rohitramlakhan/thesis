FME workspace cs1_dwg2ifc_(1).fmw

Parameters:
- SourceDataset_ACAD = $(FME_MF_DIR)MR_telecommunication_cables.dwg   # Source Autodesk AutoCAD DWG/DXF File(s)
- DestDataset_IFC = $(FME_MF_DIR)telecom_rotterdam.ifc   # Destination Industry Foundation Class (IFC) File(s)

Readers:
- ACAD_1: ACAD from $(SourceDataset_ACAD)

Writers:
- IFC_1: IFC to $(DestDataset_IFC)

Bookmark: DWG model
C3D-PIPE (reader ACAD_1)
    -> CommonLocalReprojector

Bookmark: Georeference
CommonLocalReprojector
    PROJECTION_TYPE = Equidistant (AZMED)
    VERTICAL_HANDLING = Ignore heights and leave them unchanged
    -> CoordinateSystemExtractor
CoordinateSystemExtractor
    CRDSYS_ATTR = _coordsys
    -> StringSearcher
StringSearcher
    CASE = no
    MATCHED_PARTS_ATTR = _matches
    MATCHED_RESULT_ATTR = _first_match
    REGEXP = _([-]*[\d]+[\.][\d]*)
    STRING_TO_SEARCH = @Value(_coordsys)
    MATCHED -> ElevationExtractor
ElevationExtractor
    ELE_ATTR = _elevation
    -> AttributeCreator
AttributeCreator
    ATTR_TABLE:
      SET_TO RefLatitude = @Value(_matches{1}.part)
      SET_TO RefLongitude = @Value(_matches{0}.part)
      SET_TO RefElevation = @Value(_elevation)
    -> AttributeExposer
AttributeExposer
    ATTR_LIST = autocad_entity_handle,fme_feature_type
    -> GeometryPropertySetter
    -> Sampler_4
    -> GeometryRemover
    -> Sampler
    -> Sampler_2
    -> Sampler_3

Bookmark: Site
Sampler
    RATE = 1
    SAMPLE_MODE = No
    SAMPLE_TYPE_LONG = First N Features
    SAMPLED -> IfcSite (writer IFC_1)
IfcSite (writer IFC_1)

Bookmark: Building
Sampler_2
    GROUP_BY = fme_feature_type
    RATE = 1
    SAMPLE_MODE = No
    SAMPLE_TYPE_LONG = First N Features
    SAMPLED -> AttributeCreator_2
AttributeCreator_2
    ATTR_TABLE = SET_TO ifc_id = Building
    -> IfcBuilding (writer IFC_1)
IfcBuilding (writer IFC_1)

Bookmark: Building Storey
Sampler_3
    GROUP_BY = fme_feature_type
    RATE = 1
    SAMPLE_MODE = No
    SAMPLE_TYPE_LONG = First N Features
    SAMPLED -> AttributeCreator_3
AttributeCreator_3
    ATTR_TABLE:
      SET_TO ifc_parent_id = Building
      SET_TO ifc_id = BuildingStorey
      SET_TO Name = Telecommunication cables
    -> IfcBuildingStorey (writer IFC_1)
IfcBuildingStorey (writer IFC_1)

Bookmark: Space
GeometryPropertySetter
    GEOM_NAME_FIELD = Body
    GQUERY:
      for $geom in //geometry
      where $geom/count(parent::geometry) = 0
      return number($geom/@fme_id)
    OVERWRITE_CHOICE = Yes
    SETTYPE_PARAM = Geometry Name
    SET -> Aggregator
Aggregator
    ACCUM_ATTRS_NAME = Merge Incoming Attributes
    AGGREGATE_TYPE = Homogeneous Collection (If Possible)
    GROUP_BY = autocad_entity_handle
    MODE = Geometry - Assemble One Level
    ORDERED = No
    SEP = ,
    AGGREGATE -> AttributeCreator__4
AttributeCreator__4
    ATTR_TABLE:
      SET_TO ifc_parent_id = BuildingStorey
      SET_TO Name = Telecommunication cable segment
      SET_TO ObjectType = Utility
    -> IfcSpace (writer IFC_1)
IfcSpace (writer IFC_1)

Bookmark: Property Set
GeometryRemover
    -> AttributeCreator_5
AttributeCreator_5
    ATTR_TABLE:
      SET_TO ifc_property_set_name = Pset_SpaceCommon
      SET_TO Category = Utility
    -> GeometryPropertySetter_2
GeometryPropertySetter_2
    OVERWRITE_CHOICE = Yes
    REMOVE_ATTRIBUTE = No
    SETTYPE_PARAM = Traits From Attributes
    SRC_ATTRS = ifc_property_set_name Category
    SET -> GeometryPropertySetter_3
GeometryPropertySetter_3
    GEOM_NAME_FIELD = IfcPropertySet
    OVERWRITE_CHOICE = Yes
    SETTYPE_PARAM = Geometry Name
    SET -> Aggregator
Sampler_4
    RATE = 1
    SAMPLE_MODE = No
    SAMPLE_TYPE_LONG = First N Features
    SAMPLED -> GeometryRemover_2
GeometryRemover_2
    -> IFCPropertySetDefinitionCreator
IFCPropertySetDefinitionCreator
    PROPERTIES_TABLE = Category IfcPropertySingleValue IfcLabel
    PSET_NAME = Pset_SpaceCommon
    -> PropertyDefinitionSet (writer IFC_1)
PropertyDefinitionSet (writer IFC_1)
