FME workspace cs1_ifc2postgis_(2).fmw

Parameters:
- SourceDataset_IFC = $(FME_MF_DIR)telecom_rotterdam.ifc   # Source Industry Foundation Class (IFC) File(s)
- DestDataset_POSTGIS = case_rotterdam   # Connection

Readers:
- IFC_1: IFC from $(SourceDataset_IFC)

Writers:
- POSTGIS_1: POSTGIS to $(DestDataset_POSTGIS)

Bookmark: IFC model
IfcSpace (reader IFC_1)
    attributes: GlobalId char(22), Name string, Description string, ObjectType string, LongName string, CompositionType enumeration, InteriorOrExteriorSpace enumeration, ElevationWithFlooring real, Annotation geometry, Axis geometry, Body geometry, ifc_type_object_id string
    -> AttributeExposer

Bookmark: Cable segment
AttributeExposer
    ATTR_LIST = ifc_instance_name
    -> AttributeFilter
AttributeFilter
    ATTR_NAME = ifc_instance_name
    ATTR_VALUES = <Empty>,<Missing>,<Null>,<Unfiltered>,250023
    250023 -> AttributeManager

Bookmark: PostGIS
AttributeManager
    ATTR_TABLE:
      RENAME_SET_VALUE GlobalId > globalid
      RENAME_SET_VALUE Name > name
      RENAME_SET_VALUE Description > description
      RENAME_SET_VALUE LongName > longname
      RENAME_SET_VALUE ObjectType > objecttype
      RENAME_SET_VALUE CompositionType > compositiontype
      RENAME_SET_VALUE InteriorOrExteriorSpace > interiororexteriorspace
      RENAME_SET_VALUE ElevationWithFlooring > elevationwithflooring
      RENAME_SET_VALUE Annotation > annotation
      RENAME_SET_VALUE Axis > axis
      RENAME_SET_VALUE Body > body
    -> telecom_rotterdam (writer POSTGIS_1)
telecom_rotterdam (writer POSTGIS_1)
    attributes: globalid char(22), name text, description text, objecttype text, longname text, compositiontype text, interiororexteriorspace text, elevationwithflooring float8, annotation text, axis text, body text, ifc_parent_id text, ifc_parent_unique_id text, ifc_type_object_id text, ifc_unique_id text
