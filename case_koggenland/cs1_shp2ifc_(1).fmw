FME workspace cs1_shp2ifc_(1).fmw

Parameters:
- SourceDataset_SHAPEFILE = $(FME_MF_DIR)drainage_koggenland.shp   # Source Esri Shapefile(s)
- DestDataset_IFC = $(FME_MF_DIR)drainage_koggenland.ifc   # Destination Industry Foundation Class (IFC) File(s)

Readers:
- SHAPEFILE_1: SHAPEFILE from $(SourceDataset_SHAPEFILE)

Writers:
- IFC_1: IFC to $(DestDataset_IFC)

Bookmark: SHP model
drainage_koggenland (reader SHAPEFILE_1)
    attributes: OBJECTID long, GLOBALID varchar(38), DATUMPLAAT date, DIAMETERMM long, PLANJAAR long, RESTLEVENS long, MATERIAALT varchar(254), IDENTIFICA varchar(254), TYPESPEC varchar(254), VERWERKING varchar(254), GISIB_ID long, AD_ID varchar(254), OBJECTBEGI date, OBJECTEIND date, CREATED_US varchar(254), CREATED_DA date, LAST_EDITE varchar(50), LAST_EDI_1 date, BEHEERDER varchar(254), ONDERHOUDE varchar(254), EIGENAAR varchar(254), DATALEVERA varchar(254), INNETWERK varchar(254), HUIDIGESTA varchar(50), IMKL_INNET varchar(254), VERTICALE_ long, AFVALWATER varchar(254), INDICATIEV varchar(1), EISVOORZOR long, DIEPTELEGG varchar(254),
      LENGTE double, OPMERKING varchar(254), SHAPE_STLe double
    -> CommonLocalReprojector

Bookmark: Extract RefLatitude, RefLongitude and RefElevation
CommonLocalReprojector
    PROJECTION_TYPE = Equidistant (AZMED)
    VERTICAL_HANDLING = Ignore heights and leave them unchanged
    -> CoordinateSystemExtractor
CoordinateSystemExtractor
    CRDSYS_ATTR = _coordsys
    -> StringSearcher
StringSearcher
    CASE = no
    MATCHED_PARTS_ATTR = _matches
    MATCHED_RESULT_ATTR = _first_match
    REGEXP = _([-]*[\d]+[\.][\d]*)
    STRING_TO_SEARCH = @Value(_coordsys)
    MATCHED -> ElevationExtractor
ElevationExtractor
    ELE_ATTR = _elevation
    -> AttributeCreator
AttributeCreator
    ATTR_TABLE:
      SET_TO RefLatitude = @Value(_matches{1}.part)
      SET_TO RefLongitude = @Value(_matches{0}.part)
      SET_TO RefElevation = -@Value(DIEPTELEGG)
    -> AttributeExposer
AttributeExposer
    ATTR_LIST = fme_feature_type
    -> Bufferer
    -> Sampler_4
    -> GeometryRemover
    -> Sampler
    -> Sampler_2
    -> Sampler_3

Bookmark: Site
Sampler
    RATE = 1
    SAMPLE_MODE = No
    SAMPLE_TYPE_LONG = First N Features
    SAMPLED -> IfcSite (writer IFC_1)
IfcSite (writer IFC_1)
    attributes: OBJECTID int, GLOBALID varchar(38), DIAMETERMM int, PLANJAAR int, RESTLEVENS int, MATERIAALT varchar(254), IDENTIFICA varchar(254), TYPESPEC varchar(254), VERWERKING varchar(254), GISIB_ID int, AD_ID varchar(254), CREATED_US varchar(254), LAST_EDITE varchar(50), BEHEERDER varchar(254), ONDERHOUDE varchar(254), EIGENAAR varchar(254), DATALEVERA varchar(254), INNETWERK varchar(254), HUIDIGESTA varchar(50), IMKL_INNET varchar(254), VERTICALE_ int, AFVALWATER varchar(254), INDICATIEV varchar(1), EISVOORZOR int, DIEPTELEGG varchar(254), LENGTE number, OPMERKING varchar(254), SHAPE_STLe number

Bookmark: Building
Sampler_2
    GROUP_BY = fme_feature_type
    RATE = 1
    SAMPLE_MODE = No
    SAMPLE_TYPE_LONG = First N Features
    SAMPLED -> AttributeCreator_2
AttributeCreator_2
    ATTR_TABLE = SET_TO ifc_id = Building
    -> IfcBuilding (writer IFC_1)
IfcBuilding (writer IFC_1)
    attributes: OBJECTID int, GLOBALID varchar(38), DIAMETERMM int, PLANJAAR int, RESTLEVENS int, MATERIAALT varchar(254), IDENTIFICA varchar(254), TYPESPEC varchar(254), VERWERKING varchar(254), GISIB_ID int, AD_ID varchar(254), CREATED_US varchar(254), LAST_EDITE varchar(50), BEHEERDER varchar(254), ONDERHOUDE varchar(254), EIGENAAR varchar(254), DATALEVERA varchar(254), INNETWERK varchar(254), HUIDIGESTA varchar(50), IMKL_INNET varchar(254), VERTICALE_ int, AFVALWATER varchar(254), INDICATIEV varchar(1), EISVOORZOR int, DIEPTELEGG varchar(254), LENGTE number, OPMERKING varchar(254), SHAPE_STLe number

Bookmark: Building Storey
Sampler_3
    GROUP_BY = fme_feature_type
    RATE = 1
    SAMPLE_MODE = No
    SAMPLE_TYPE_LONG = First N Features
    SAMPLED -> AttributeCreator_3
AttributeCreator_3
    ATTR_TABLE:
      SET_TO ifc_parent_id = Building
      SET_TO ifc_id = BuildingStorey
      SET_TO Name = Rainwater drainage pipe
    -> IfcBuildingStorey (writer IFC_1)
IfcBuildingStorey (writer IFC_1)
    attributes: OBJECTID int, GLOBALID varchar(38), DIAMETERMM int, PLANJAAR int, RESTLEVENS int, MATERIAALT varchar(254), IDENTIFICA varchar(254), TYPESPEC varchar(254), VERWERKING varchar(254), GISIB_ID int, AD_ID varchar(254), CREATED_US varchar(254), LAST_EDITE varchar(50), BEHEERDER varchar(254), ONDERHOUDE varchar(254), EIGENAAR varchar(254), DATALEVERA varchar(254), INNETWERK varchar(254), HUIDIGESTA varchar(50), IMKL_INNET varchar(254), VERTICALE_ int, AFVALWATER varchar(254), INDICATIEV varchar(1), EISVOORZOR int, DIEPTELEGG varchar(254), LENGTE number, OPMERKING varchar(254), SHAPE_STLe number

Bookmark: Space
Bufferer
    MODE = SOLID
    OFFSET = 0.1
    SPHERE_DIVISIONS = 2
    BUFFERED -> GeometryPropertySetter
GeometryPropertySetter
    GEOM_NAME_FIELD = Body
    GQUERY:
      for $geom in //geometry
      where $geom/count(parent::geometry) = 0
      return number($geom/@fme_id)
    OVERWRITE_CHOICE = Yes
    SETTYPE_PARAM = Geometry Name
    SET -> Aggregator
Aggregator
    ACCUM_ATTRS_NAME = Merge Incoming Attributes
    AGGREGATE_TYPE = Homogeneous Collection (If Possible)
    GROUP_BY = AD_ID
    MODE = Geometry - Assemble One Level
    ORDERED = No
    SEP = ,
    AGGREGATE -> AttributeCreator__4
AttributeCreator__4
    ATTR_TABLE:
      SET_TO ifc_parent_id = BuildingStorey
      SET_TO Name = @Value(OBJECTID)
      SET_TO ObjectType = Utility
    -> IfcSpace (writer IFC_1)
IfcSpace (writer IFC_1)
    attributes: OBJECTID int, GLOBALID varchar(38), DIAMETERMM int, PLANJAAR int, RESTLEVENS int, MATERIAALT varchar(254), IDENTIFICA varchar(254), TYPESPEC varchar(254), VERWERKING varchar(254), GISIB_ID int, AD_ID varchar(254), CREATED_US varchar(254), LAST_EDITE varchar(50), BEHEERDER varchar(254), ONDERHOUDE varchar(254), EIGENAAR varchar(254), DATALEVERA varchar(254), INNETWERK varchar(254), HUIDIGESTA varchar(50), IMKL_INNET varchar(254), VERTICALE_ int, AFVALWATER varchar(254), INDICATIEV varchar(1), EISVOORZOR int, DIEPTELEGG varchar(254), LENGTE number, OPMERKING varchar(254), SHAPE_STLe number

Bookmark: Property Set
GeometryRemover
    -> AttributeCreator_5
AttributeCreator_5
    ATTR_TABLE:
      SET_TO ifc_property_set_name = Pset_SpaceCommon
      SET_TO Category = Utility
    -> GeometryPropertySetter_2
GeometryPropertySetter_2
    OVERWRITE_CHOICE = Yes
    REMOVE_ATTRIBUTE = No
    SETTYPE_PARAM = Traits From Attributes
    SRC_ATTRS = ifc_property_set_name Category
    SET -> GeometryPropertySetter_3
GeometryPropertySetter_3
    GEOM_NAME_FIELD = IfcPropertySet
    OVERWRITE_CHOICE = Yes
    SETTYPE_PARAM = Geometry Name
    SET -> Aggregator
Sampler_4
    RATE = 1
    SAMPLE_MODE = No
    SAMPLE_TYPE_LONG = First N Features
    SAMPLED -> GeometryRemover_2
GeometryRemover_2
    -> IFCPropertySetDefinitionCreator
IFCPropertySetDefinitionCreator
    PROPERTIES_TABLE = Category IfcPropertySingleValue IfcLabel
    PSET_NAME = Pset_SpaceCommon
    -> PropertySetDefinition (writer IFC_1)
PropertySetDefinition (writer IFC_1)
    attributes: OBJECTID int, GLOBALID varchar(38), DIAMETERMM int, PLANJAAR int, RESTLEVENS int, MATERIAALT varchar(254), IDENTIFICA varchar(254), TYPESPEC varchar(254), VERWERKING varchar(254), GISIB_ID int, AD_ID varchar(254), CREATED_US varchar(254), LAST_EDITE varchar(50), BEHEERDER varchar(254), ONDERHOUDE varchar(254), EIGENAAR varchar(254), DATALEVERA varchar(254), INNETWERK varchar(254), HUIDIGESTA varchar(50), IMKL_INNET varchar(254), VERTICALE_ int, AFVALWATER varchar(254), INDICATIEV varchar(1), EISVOORZOR int, DIEPTELEGG varchar(254), LENGTE number, OPMERKING varchar(254), SHAPE_STLe number
