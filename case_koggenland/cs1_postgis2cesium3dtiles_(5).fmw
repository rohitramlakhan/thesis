FME workspace cs1_postgis2cesium3dtiles_(5).fmw

Parameters:
- SourceDataset_POSTGIS = case_koggenland   # Connection
- DestDataset_CESIUM3DTILES = C:\Users\rohit\Documents\Rohit\GEO2020\Case studies\Case study 2 - North Holland   # Destination Cesium 3D Tiles Folder

Readers:
- POSTGIS_1: POSTGIS from $(SourceDataset_POSTGIS)

Writers:
- CESIUM3DTILES_1: CESIUM3DTILES to $(DestDataset_CESIUM3DTILES)

Bookmark: Rainwater drainage pipe segment
drainage_koggenland (reader POSTGIS_1)
    attributes: globalid char(22), name text, description text, objecttype text, longname text, compositiontype text, interiororexteriorspace text, elevationwithflooring float8, annotation text, axis text, body text, ifc_parent_id text, ifc_parent_unique_id text, ifc_type_object_id text, ifc_unique_id text, party varchar(80), rights varchar(80), restrictions varchar(80), responsibilities varchar(80)
    -> GeometryColorSetter

Bookmark: Colour
GeometryColorSetter
    ALPHA = 0.5
    FILL_COLOR = 0.666667,1,1
    MODE = Fixed
    REC = Yes
    SIDE = Both
    COLORED -> public.drainage_koggenland (writer CESIUM3DTILES_1)
GeometryColorSetter_2
    ALPHA = 0.5
    FILL_COLOR = 1,1,0
    MODE = Fixed
    REC = Yes
    SIDE = Both
    COLORED -> public.parcels_koggenland (writer CESIUM3DTILES_1)

Bookmark: Cesium 3D Tiles
public.drainage_koggenland (writer CESIUM3DTILES_1)
    attributes: globalid string, name string, description string, objecttype string, longname string, compositiontype string, interiororexteriorspace string, elevationwithflooring float, annotation string, axis string, body string, ifc_parent_id string, ifc_parent_unique_id string, ifc_type_object_id string, ifc_unique_id string, party string, rights string, restrictions string, responsibilities string

Bookmark: Parcels
parcels_koggenland (reader POSTGIS_1)
    attributes: globalid char(22), name text, description text, objecttype text, longname text, compositiontype text, interiororexteriorspace text, elevationwithflooring float8, annotation text, axis text, body text, ifc_parent_id text, ifc_parent_unique_id text, ifc_type_object_id text, ifc_unique_id text, party varchar(80), rights varchar(80), restrictions varchar(80), responsibilities varchar(80)
    -> GeometryColorSetter_2

Bookmark: Cesium 3D Tiles
public.parcels_koggenland (writer CESIUM3DTILES_1)
    attributes: globalid string, name string, description string, objecttype string, longname string, compositiontype string, interiororexteriorspace string, elevationwithflooring float, annotation string, axis string, body string, ifc_parent_id string, ifc_parent_unique_id string, ifc_type_object_id string, ifc_unique_id string, party string, rights string, restrictions string, responsibilities string
