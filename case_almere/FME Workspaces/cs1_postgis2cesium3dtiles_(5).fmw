FME workspace cs1_postgis2cesium3dtiles_(5).fmw

Parameters:
- SourceDataset_POSTGIS = case_almere   # Connection
- DestDataset_CESIUM3DTILES = C:\Users\rohit\Documents\Rohit\GEO2020\Case studies\Case study 1 - Almere   # Destination Cesium 3D Tiles Folder

Readers:
- POSTGIS_1: POSTGIS from $(SourceDataset_POSTGIS)

Writers:
- CESIUM3DTILES_1: CESIUM3DTILES to $(DestDataset_CESIUM3DTILES)

Bookmark: PostGIS - Home connections
home_connections_almere (reader POSTGIS_1)
    attributes: globalid char(22), name text, description text, objecttype text, longname text, compositiontype text, interiororexteriorspace text, elevationwithflooring float8, annotation text, axis text, body text, ifc_parent_id text, ifc_parent_unique_id text, ifc_type_object_id text, ifc_unique_id text, party varchar(80), rights varchar(80), restrictions varchar(80), responsibilities varchar(80)
    -> GeometryColorSetter_3

Bookmark: Colour
GeometryColorSetter_3
    ALPHA = 0.5
    FILL_COLOR = 1,0.792157,0.988235
    MODE = Fixed
    REC = Yes
    SIDE = Both
    COLORED -> public.home_connections_almere (writer CESIUM3DTILES_1)
GeometryColorSetter
    ALPHA = 0.5
    FILL_COLOR = 0.666667,1,1
    MODE = Fixed
    REC = Yes
    SIDE = Both
    COLORED -> public.main_sewage_almere (writer CESIUM3DTILES_1)
GeometryColorSetter_2
    ALPHA = 0.4
    FILL_COLOR = 1,1,0
    MODE = Fixed
    REC = Yes
    SIDE = Both
    COLORED -> public.parcels_almere (writer CESIUM3DTILES_1)

Bookmark: Cesium 3D Tiles
public.home_connections_almere (writer CESIUM3DTILES_1)
    attributes: globalid string, name string, description string, objecttype string, longname string, compositiontype string, interiororexteriorspace string, elevationwithflooring float, annotation string, axis string, body string, ifc_parent_id string, ifc_parent_unique_id string, ifc_type_object_id string, ifc_unique_id string, party string, rights string, restrictions string, responsibilities string

Bookmark: PostGIS - Main sewage system
main_sewage_almere (reader POSTGIS_1)
    attributes: globalid char(22), name text, description text, objecttype text, longname text, compositiontype text, interiororexteriorspace text, elevationwithflooring float8, annotation text, axis text, body text, ifc_parent_id text, ifc_parent_unique_id text, ifc_type_object_id text, ifc_unique_id text, party varchar(80), rights varchar(80), restrictions varchar(80), responsibilities varchar(80)
    -> GeometryColorSetter

Bookmark: Cesium 3D Tiles
public.main_sewage_almere (writer CESIUM3DTILES_1)
    attributes: globalid string, name string, description string, objecttype string, longname string, compositiontype string, interiororexteriorspace string, elevationwithflooring float, annotation string, axis string, body string, ifc_parent_id string, ifc_parent_unique_id string, ifc_type_object_id string, ifc_unique_id string, party string, rights string, restrictions string, responsibilities string

Bookmark: PostGIS Parcels
parcels_almere (reader POSTGIS_1)
    attributes: globalid char(22), name text, description text, objecttype text, longname text, compositiontype text, interiororexteriorspace text, elevationwithflooring float8, annotation text, axis text, body text, ifc_parent_id text, ifc_parent_unique_id text, ifc_type_object_id text, ifc_unique_id text, party varchar(80), rights varchar(80), restrictions varchar(80), responsibilities varchar(80)
    -> GeometryColorSetter_2

Bookmark: Cesium 3D Tiles
public.parcels_almere (writer CESIUM3DTILES_1)
    attributes: globalid string, name string, description string, objecttype string, longname string, compositiontype string, interiororexteriorspace string, elevationwithflooring float, annotation string, axis string, body string, ifc_parent_id string, ifc_parent_unique_id string, ifc_type_object_id string, ifc_unique_id string, party string, rights string, restrictions string, responsibilities string
