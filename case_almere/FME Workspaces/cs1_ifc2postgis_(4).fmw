FME workspace cs1_ifc2postgis_(4).fmw

Parameters:
- SourceDataset_IFC = $(FME_MF_DIR)parcels_almere.ifc   # Source Industry Foundation Class (IFC) File(s)
- DestDataset_POSTGIS = case_almere   # Connection
- SourceDataset_IFC_4 = $(FME_MF_DIR)main_sewage_almere.ifc   # Source Industry Foundation Class (IFC) File(s)
- SourceDataset_IFC_5 = $(FME_MF_DIR)home_connections_almere.ifc   # Source Industry Foundation Class (IFC) File(s)

Readers:
- IFC_1: IFC from $(SourceDataset_IFC)
- IFC_2: IFC from $(SourceDataset_IFC_4)
- IFC_3: IFC from $(SourceDataset_IFC_5)

Writers:
- POSTGIS_1: POSTGIS to $(DestDataset_POSTGIS)

Bookmark: IFC model - Main sewage
IfcSpace (reader IFC_2)
    attributes: GlobalId char(22), Name string, Description string, ObjectType string, LongName string, CompositionType enumeration, InteriorOrExteriorSpace enumeration, ElevationWithFlooring real, Annotation geometry, Axis geometry, Body geometry, ifc_type_object_id string
    -> AttributeManager

Bookmark: PostGIS
AttributeManager
    ATTR_TABLE:
      RENAME_SET_VALUE GlobalId > globalid
      RENAME_SET_VALUE Name > name
      RENAME_SET_VALUE Description > description
      RENAME_SET_VALUE LongName > longname
      RENAME_SET_VALUE ObjectType > objecttype
      RENAME_SET_VALUE CompositionType > compositiontype
      RENAME_SET_VALUE InteriorOrExteriorSpace > interiororexteriorspace
      RENAME_SET_VALUE ElevationWithFlooring > elevationwithflooring
      RENAME_SET_VALUE Annotation > annotation
      RENAME_SET_VALUE Axis > axis
      RENAME_SET_VALUE Body > body
    -> main_sewage_almere (writer POSTGIS_1)
main_sewage_almere (writer POSTGIS_1)
    attributes: globalid char(22), name text, description text, objecttype text, longname text, compositiontype text, interiororexteriorspace text, elevationwithflooring float8, annotation text, axis text, body text, ifc_parent_id text, ifc_parent_unique_id text, ifc_type_object_id text, ifc_unique_id text

Bookmark: IFC model - Home connections
IfcSpace (reader IFC_3)
    attributes: GlobalId char(22), Name string, Description string, ObjectType string, LongName string, CompositionType enumeration, InteriorOrExteriorSpace enumeration, ElevationWithFlooring real, Annotation geometry, Axis geometry, Body geometry, ifc_type_object_id string
    -> AttributeManager_3

Bookmark: PostGIS
AttributeManager_3
    ATTR_TABLE:
      RENAME_SET_VALUE GlobalId > globalid
      RENAME_SET_VALUE Name > name
      RENAME_SET_VALUE Description > description
      RENAME_SET_VALUE LongName > longname
      RENAME_SET_VALUE ObjectType > objecttype
      RENAME_SET_VALUE CompositionType > compositiontype
      RENAME_SET_VALUE InteriorOrExteriorSpace > interiororexteriorspace
      RENAME_SET_VALUE ElevationWithFlooring > elevationwithflooring
      RENAME_SET_VALUE Annotation > annotation
      RENAME_SET_VALUE Axis > axis
      RENAME_SET_VALUE Body > body
    -> home_connections_almere (writer POSTGIS_1)
home_connections_almere (writer POSTGIS_1)
    attributes: globalid char(22), name text, description text, objecttype text, longname text, compositiontype text, interiororexteriorspace text, elevationwithflooring float8, annotation text, axis text, body text, ifc_parent_id text, ifc_parent_unique_id text, ifc_type_object_id text, ifc_unique_id text

Bookmark: IFC model - parcels
IfcSpace (reader IFC_1)
    attributes: GlobalId char(22), Name string, Description string, ObjectType string, LongName string, CompositionType enumeration, InteriorOrExteriorSpace enumeration, ElevationWithFlooring real, Annotation geometry, Axis geometry, Body geometry, ifc_type_object_id string
    -> AttributeManager_2

Bookmark: PostGIS
AttributeManager_2
    ATTR_TABLE:
      RENAME_SET_VALUE GlobalId > globalid
      RENAME_SET_VALUE Name > name
      RENAME_SET_VALUE Description > description
      RENAME_SET_VALUE LongName > longname
      RENAME_SET_VALUE ObjectType > objecttype
      RENAME_SET_VALUE CompositionType > compositiontype
      RENAME_SET_VALUE InteriorOrExteriorSpace > interiororexteriorspace
      RENAME_SET_VALUE ElevationWithFlooring > elevationwithflooring
      RENAME_SET_VALUE Annotation > annotation
      RENAME_SET_VALUE Axis > axis
      RENAME_SET_VALUE Body > body
    -> parcels_almere (writer POSTGIS_1)
parcels_almere (writer POSTGIS_1)
    attributes: globalid char(22), name text, description text, objecttype text, longname text, compositiontype text, interiororexteriorspace text, elevationwithflooring float8, annotation text, axis text, body text, ifc_parent_id text, ifc_parent_unique_id text, ifc_type_object_id text, ifc_unique_id text
