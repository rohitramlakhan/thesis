FME workspace cs1_shp2ifc_(2).fmw

Parameters:
- SourceDataset_SHAPEFILE = $(FME_MF_DIR)home_connections_almere.shp   # Source Esri Shapefile(s)
- DestDataset_IFC = $(FME_MF_DIR)home_connections_almere.ifc   # Destination Industry Foundation Class (IFC) File(s)

Readers:
- SHAPEFILE_1: SHAPEFILE from $(SourceDataset_SHAPEFILE)

Writers:
- IFC_1: IFC to $(DestDataset_IFC)

Bookmark: SHP model
home_connections_almere (reader SHAPEFILE_1)
    attributes: id number(20,0), NAAM varchar(254), TYPE_AANSL varchar(254), DIAMETER number(20,0), STELSEL varchar(254)
    -> CommonLocalReprojector

Bookmark: Extract RefLatitude, RefLongitude and RefElevation
CommonLocalReprojector
    PROJECTION_TYPE = Equidistant (AZMED)
    VERTICAL_HANDLING = Ignore heights and leave them unchanged
    -> CoordinateSystemExtractor
CoordinateSystemExtractor
    CRDSYS_ATTR = _coordsys
    -> StringSearcher
StringSearcher
    CASE = no
    MATCHED_PARTS_ATTR = _matches
    MATCHED_RESULT_ATTR = _first_match
    REGEXP = _([-]*[\d]+[\.][\d]*)
    STRING_TO_SEARCH = @Value(_coordsys)
    MATCHED -> ElevationExtractor
ElevationExtractor
    ELE_ATTR = _elevation
    -> AttributeCreator
AttributeCreator
    ATTR_TABLE:
      SET_TO RefLatitude = @Value(_matches{1}.part)
      SET_TO RefLongitude = @Value(_matches{0}.part)
      SET_TO RefElevation = @Value(_elevation)
    -> AttributeExposer
AttributeExposer
    ATTR_LIST = fme_feature_type
    -> Bufferer
    -> Sampler_4
    -> GeometryRemover
    -> Sampler
    -> Sampler_2
    -> Sampler_3

Bookmark: Site
Sampler
    RATE = 1
    SAMPLE_MODE = No
    SAMPLE_TYPE_LONG = First N Features
    SAMPLED -> IfcSite (writer IFC_1)
IfcSite (writer IFC_1)
    attributes: NAAM varchar(254), TYPE_AANSL varchar(254), STELSEL varchar(254)

Bookmark: Building
Sampler_2
    GROUP_BY = fme_feature_type
    RATE = 1
    SAMPLE_MODE = No
    SAMPLE_TYPE_LONG = First N Features
    SAMPLED -> AttributeCreator_2
AttributeCreator_2
    ATTR_TABLE = SET_TO ifc_id = Building
    -> IfcBuilding (writer IFC_1)
IfcBuilding (writer IFC_1)
    attributes: NAAM varchar(254), TYPE_AANSL varchar(254), STELSEL varchar(254)

Bookmark: Building Storey
Sampler_3
    GROUP_BY = fme_feature_type
    RATE = 1
    SAMPLE_MODE = No
    SAMPLE_TYPE_LONG = First N Features
    SAMPLED -> AttributeCreator_3
AttributeCreator_3
    ATTR_TABLE:
      SET_TO ifc_parent_id = Building
      SET_TO ifc_id = BuildingStorey
      SET_TO Name = Sewage drain pipe
    -> IfcBuildingStorey (writer IFC_1)
IfcBuildingStorey (writer IFC_1)
    attributes: NAAM varchar(254), TYPE_AANSL varchar(254), STELSEL varchar(254)

Bookmark: Space
Bufferer
    MODE = SOLID
    OFFSET = 0.125
    SPHERE_DIVISIONS = 2
    BUFFERED -> Offsetter
Offsetter
    MODE = Cartesian Coordinate
    XOFF = 0
    YOFF = 0
    ZOFF = -5.825
    OFFSET -> GeometryPropertySetter
GeometryPropertySetter
    GEOM_NAME_FIELD = Body
    GQUERY:
      for $geom in //geometry
      where $geom/count(parent::geometry) = 0
      return number($geom/@fme_id)
    OVERWRITE_CHOICE = Yes
    SETTYPE_PARAM = Geometry Name
    SET -> Aggregator
Aggregator
    ACCUM_ATTRS_NAME = Merge Incoming Attributes
    AGGREGATE_TYPE = Homogeneous Collection (If Possible)
    GROUP_BY = id
    MODE = Geometry - Assemble One Level
    ORDERED = No
    SEP = ,
    AGGREGATE -> AttributeCreator__4
AttributeCreator__4
    ATTR_TABLE:
      SET_TO ifc_parent_id = BuildingStorey
      SET_TO Name = @Value(NAAM)
      SET_TO ObjectType = Utility
    -> IfcSpace (writer IFC_1)
IfcSpace (writer IFC_1)
    attributes: NAAM varchar(254), TYPE_AANSL varchar(254), STELSEL varchar(254)

Bookmark: Property Set
GeometryRemover
    -> AttributeCreator_5
AttributeCreator_5
    ATTR_TABLE:
      SET_TO ifc_property_set_name = Pset_SpaceCommon
      SET_TO Category = Utility
    -> GeometryPropertySetter_2
GeometryPropertySetter_2
    OVERWRITE_CHOICE = Yes
    REMOVE_ATTRIBUTE = No
    SETTYPE_PARAM = Traits From Attributes
    SRC_ATTRS = ifc_property_set_name Category
    SET -> GeometryPropertySetter_3
GeometryPropertySetter_3
    GEOM_NAME_FIELD = IfcPropertySet
    OVERWRITE_CHOICE = Yes
    SETTYPE_PARAM = Geometry Name
    SET -> Aggregator
Sampler_4
    RATE = 1
    SAMPLE_MODE = No
    SAMPLE_TYPE_LONG = First N Features
    SAMPLED -> GeometryRemover_2
GeometryRemover_2
    -> IFCPropertySetDefinitionCreator
IFCPropertySetDefinitionCreator
    PROPERTIES_TABLE = Category IfcPropertySingleValue IfcLabel
    PSET_NAME = Pset_SpaceCommon
    -> IfcPropertySet (writer IFC_1)
IfcPropertySet (writer IFC_1)
    attributes: NAAM varchar(254), TYPE_AANSL varchar(254), STELSEL varchar(254)
